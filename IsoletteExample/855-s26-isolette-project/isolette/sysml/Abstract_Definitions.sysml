// Abstract_Definitions.sysml
package Abstract_Definitions {

  private import HAMR::*;
  private import Isolette_Properties::*;

  // Abstract periodic thread serving as the base type for all application threads.
  // Corresponds to AADL Abstract_Definitions::Periodic_Thread, which all thread
  // types in this model extend.  Period matches Isolette_Properties::ThreadPeriod (1000ms).
  abstract part def Periodic_Thread :> Thread {
    attribute :>> Dispatch_Protocol = Supported_Dispatch_Protocols::Periodic;

    attribute :>> Period = 1000[ms];

    attribute :>> Compute_Execution_Time = 60 [ms] .. 60[ms] as Timing_Properties::Compute_Execution_Time;
  }

  abstract part def Periodic_Rust_Thread :> Periodic_Thread {
    attribute :>> Implementation_Language = Rust;
  }
}
